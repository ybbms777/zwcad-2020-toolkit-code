(vl-load-com)
(setvar "ACADLSPASDOC" 1)
;; zwk:root is supplied by the installer/startup hook, never *load-truename*.
;; Distribution file is GBK encoded.
(defun zwk:bridge (cmd / path f value)
  (setq path (strcat (getenv "TEMP") "/zwkit-bridge-102.txt"))
  (if (findfile path) (vl-file-delete path))
  (command cmd)
  (if (setq f (open path "r"))
    (progn (setq value (read (read-line f))) (close f) value)
    nil))
(defun zwk:ready () (equal (zwk:bridge "ZWKREADY102") '("READY")))
;; ACADLSPASDOC=1：本文件在「每张图」打开时都会跑一遍（LISP 命令是按图纸隔离的，必须这样）。
;; VIEWRES 存在图纸里，改它会把图纸标成「已修改」—— 客户图纸一打开就问要不要保存。
;; 用 acad-push-dbmod / acad-pop-dbmod 包起来，改完不算修改（2026-09-22 真机确认 ZWCAD 2020 有这两个函数，
;; 对照：不包 DBMOD=1，包了 DBMOD=0）。
;; 注意 ZWCAD 没有 VIEWRES 系统变量，(getvar "VIEWRES") 恒为 nil —— 原来的「已是 20000 就跳过」从没生效过，
;; 现在改用 DLL 读出的当前平滑度（zwk:smooth-value）判断。
(defun zwk:smooth (/ old v push)
  (setq v (vl-catch-all-apply 'zwk:smooth-value nil))
  (if (vl-catch-all-error-p v) (setq v nil))
  (if (or (null v) (/= v 10000))
    (progn
      (setq old (getvar "CMDECHO")
            push (and acad-push-dbmod acad-pop-dbmod))
      (setvar "CMDECHO" 0)
      (if push (vl-catch-all-apply 'acad-push-dbmod nil))
      (command "_.VIEWRES" "_Y" 10000)
      (if push (vl-catch-all-apply 'acad-pop-dbmod nil))
      (setvar "CMDECHO" old))))
(defun zwk:smooth-value () (zwk:bridge "ZWKSMOOTH102"))
(defun zwk:selection-ok ()
  (and zwk:enabled
    (or (not (member "dimensions" zwk:enabled)) c:ZD)
    (or (not (member "trim" zwk:enabled)) c:TR)
    (or (not (member "extend" zwk:enabled)) c:EX)
    (or (not (member "tolerance" zwk:enabled)) c:GC)
    (or (not (member "symbols" zwk:enabled)) c:FH)
    (or (not (member "font" zwk:enabled)) c:ZF)
    (or (not (member "dimline" zwk:enabled)) c:BZ)
    (or (not (member "frame" zwk:enabled)) c:TK)
    (or (not (member "tke" zwk:enabled)) c:TKE)
    (or (not (member "proccalc" zwk:enabled)) c:JSQ)))
(defun zwk:enabled-str (/ s)
  (setq s "")
  (foreach zwk:e zwk:enabled (setq s (strcat s zwk:e " ")))
  (if (= s "") "无" s))
;; 从 version.json 读版本号（纯字符串扫描，不用 VL 函数；任何异常都回退 "1.2"）。
;; version.json 里该行格式固定为：  "version": "1.2.28",
(defun zwk:ver (/ f ln v i n done)
  (setq v nil done nil)
  (setq f (vl-catch-all-apply 'open (list (strcat zwk:root "/version.json") "r")))
  (if (and (not (vl-catch-all-error-p f)) f)
    (progn
      (while (and (not done) (setq ln (read-line f)))
        (if (wcmatch ln "*\"version\":*")
          (progn
            (setq n (strlen ln) i n)
            (while (and (> i 0) (/= (substr ln i 1) "\"")) (setq i (1- i)))
            (if (> i 0)
              (progn
                (setq n (1- i) v "")
                (while (and (> n 0) (/= (substr ln n 1) "\""))
                  (setq v (strcat (substr ln n 1) v) n (1- n)))))
            (setq done T))))
      (close f)))
  (if (and v (/= v "")) v "1.2"))

(defun c:ZWKCHECK (/ sv)
  ;; 平滑度必须判空再 itoa：DLL 没加载时 zwk:smooth-value 返回 nil，
  ;; 直接 (itoa nil) 会报错 —— 而用户敲这条命令往往正是为了排查「插件没加载」（1.2.28 修的）。
  (setq sv (vl-catch-all-apply 'zwk:smooth-value nil))
  (if (vl-catch-all-error-p sv) (setq sv nil))
  (princ (strcat "\n工具包 " (zwk:ver) "，自检模块=" (if (zwk:ready) "就绪" "未就绪")
    "，平滑度=" (if (numberp sv) (itoa sv) "未知") "，已启用：" (zwk:enabled-str)))
  (princ))
(if (and zwk:root (findfile (strcat zwk:root "/modules.lsp")))
  (progn
    ;; DLL 在整个 CAD 进程里只需要载一次；第二张图起它的 LISP 函数已经在了，不再重复 NETLOAD。
    (if (not ZWK_MODULE_101)
      (command "_.NETLOAD" (strcat zwk:root "/bin/ZWKit.Core.102.dll")))
    (setq zwk:enabled '("dimensions" "trim" "extend" "tolerance" "symbols" "font" "dimline" "frame" "tke" "proccalc"))
    (if (findfile (strcat zwk:root "/selection.lsp")) (load (strcat zwk:root "/selection.lsp")))
    (load (strcat zwk:root "/modules.lsp"))
    ;; EXD's Shift-drag reuses trim.lsp's zt:trim, so picking "extend" alone
    ;; still needs trim.lsp loaded -- but ZT/TRD stay hidden below unless
    ;; "trim" itself was actually selected.
    (setq zwk:loadset zwk:enabled)
    (if (and (member "extend" zwk:loadset) (not (member "trim" zwk:loadset)))
      (setq zwk:loadset (cons "trim" zwk:loadset)))
    ;; module file -> selection key; nil key = always loaded (foundational)
    (setq zwk:modkeys '(("modules/dimensions.lsp" . "dimensions")
                         ("modules/trim.lsp" . "trim")
                         ("modules/extend.lsp" . "extend")
                         ("modules/click.lsp" . nil)
                         ("modules/dimcore.lsp" . nil)
                         ("modules/tolerance.lsp" . "tolerance")
                         ("modules/symbols.lsp" . "symbols")
                         ("modules/font.lsp" . "font")
                         ("modules/dimline.lsp" . "dimline")
                         ("modules/frame.lsp" . "frame")
                         ("modules/tkblock.lsp" . "tke")
                         ("modules/proccalc.lsp" . "proccalc")
                         ("modules/trimext.lsp" . nil)))
    (foreach zwk:m zwk:modules
      (setq zwk:key (cdr (assoc zwk:m zwk:modkeys)))
      (if (or (null zwk:key) (member zwk:key zwk:loadset))
        (load (strcat zwk:root "/" zwk:m))))
    (if (not (member "dimensions" zwk:enabled))
      (setq c:ZD nil c:ZD2 nil c:ZDO nil c:ZDB nil c:ZDJ nil c:ZDJ3 nil))
    ;; click.lsp 常驻点选版 TR/EX：已定义时不再回退原生命令。
    (if (not (member "trim" zwk:enabled))
      (progn (if (not c:TR) (defun c:TR () (command "_.TRIM") (princ))) (setq c:ZT nil c:ZTY nil c:TRD nil)))
    (if (not (member "extend" zwk:enabled))
      (progn (if (not c:EX) (defun c:EX () (command "_.EXTEND") (princ))) (setq c:EXY nil c:EXD nil)))
    (if (not (member "tolerance" zwk:enabled)) (setq c:GC nil))
    (if (not (member "symbols" zwk:enabled)) (setq c:FH nil))
    (if (not (member "font" zwk:enabled)) (setq c:ZF nil c:ZFD nil))
    (if (not (member "dimline" zwk:enabled)) (setq c:BZ nil c:BZD nil))
    (if (not (member "frame" zwk:enabled)) (setq c:TK nil c:BTK nil))
    (if (not (member "tke" zwk:enabled)) (setq c:TKE nil c:BKE nil))
    (if (not (member "proccalc" zwk:enabled)) (setq c:JSQ nil c:JSQP nil c:JSQN nil))
    (zwk:smooth)
    (princ "\n工具包已按安装选项加载，用 ZWKCHECK 自检。"))
  (princ "\n工具包路径缺失，请重新一键安装。"))
(princ)
