;;; Inline mechanical symbols using the ZGDT TrueType symbol font.
(vl-load-com)
(defun fh:code (key)
  (cdr (assoc key '(("1" . "{\\fZGDT|b1|i0|c0|p34;v}") ("2" . "{\\fZGDT|b1|i0|c0|p34;x}") ("3" . "%%c") ("4" . "{\\fZGDT|b1|i0|c0|p34;w}")))))
(defun fh:prefix (ent code / obj typ old)
  (setq obj (vlax-ename->vla-object ent) typ (cdr (assoc 0 (entget ent))))
  (cond
    ((= typ "DIMENSION")
      (setq old (vla-get-TextOverride obj))
      (if (= old "") (setq old "<>"))
      (vla-put-TextOverride obj (strcat code old))
      (vla-Update obj) T)
    ((= typ "MTEXT")
      (setq old (vla-get-TextString obj))
      (vla-put-TextString obj (strcat code old))
      (vla-Update obj) T)
    (T nil)))
(defun c:FH (/ key sel result)
  (princ "\n机械符号：1 沉孔；2 深度；3 直径；4 沉头。使用 ZGDT 字体。")
  (initget "1 2 3 4")
  (setq key (getkword "\n选择 [1/2/3/4] <1>: "))
  (if (null key) (setq key "1"))
  (if (and (/= key "3") (not (or (findfile "ZGDT.ttf") (findfile "C:/Windows/Fonts/ZGDT.ttf"))))
    (princ "\n提示：未找到 ZGDT 字体，符号可能显示为问号。可在字体安装里安装 ZGDT.ttf。"))
  (if (setq sel (entsel "\n选择标注或多行文字，将符号加在最前面: "))
    (progn
      (setq result (vl-catch-all-apply 'fh:prefix (list (car sel) (fh:code key))))
      (cond
        ((vl-catch-all-error-p result) (princ (strcat "\n未完成：" (vl-catch-all-error-message result))))
        (result (princ "\n已添加文字符号，数字字体和尺寸值保留。可撤销本次操作。"))
        (T (princ "\n请选择尺寸标注或多行文字；单行文字不支持局部字体。")))))
  (princ))
(princ "\nFH 机械符号：选择符号后点标注，自动添加文字前缀（ZGDT 字体）。")
(princ)
